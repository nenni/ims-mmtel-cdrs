MMTelChargingDataTypes {itu-t (0) identified-organization (4) etsi(0) mobileDomain (0) charging (5)
 mMTelChargingDataTypes (9) asn1Module (0) version1 (0)}

DEFINITIONS IMPLICIT TAGS ::=
BEGIN
-- EXPORTS everything

MMTelRecord ::= SET
{
	recordType 	[0] RecordType,
	retransmission	[1] NULL OPTIONAL,
	sIP-Method 	[2] SIP-Method OPTIONAL,
	role-of-Node 	[3] Role-of-Node OPTIONAL
}

RecordType ::= INTEGER
{
--  Record Value 83 is MMTel specific.
--  The contents are defined in TS 32.275 [35]
--
	mMTelRecord			(83)
}

SIP-Method ::= GraphicString

Role-of-Node ::= ENUMERATED
{
	originating (0),
	terminating (1)
}
END
